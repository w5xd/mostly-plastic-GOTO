# -*- coding: utf-8 -*-
import FreeCAD
import Mesh

FreeCAD.openDocument('./BatteryPackEnclosure.FCStd')
__objs__ = []
__objs__.append(FreeCAD.getDocument("BatteryPackEnclosure").getObject("Body004"))
Mesh.export(__objs__, u"./STL/BatteryPackEnclosure-enclosureenclosure top.stl")
del __objs__
__objs__ = []
__objs__.append(FreeCAD.getDocument("BatteryPackEnclosure").getObject("Body005"))
Mesh.export(__objs__, u"./STL/BatteryPackEnclosure-enclosureenclosure front panel.stl")
del __objs__
__objs__ = []
__objs__.append(FreeCAD.getDocument("BatteryPackEnclosure").getObject("Cut"))
Mesh.export(__objs__, u"./STL/BatteryPackEnclosure-enclosurerepaired STL exportable enclosure base.stl")

del __objs__
