# -*- coding: utf-8 -*-

import FreeCAD
import Mesh
FreeCAD.openDocument('./OnStepEnclosureAssembly.FCStd')
__objs__ = []
__objs__.append(FreeCAD.getDocument("OnStepEnclosureAssembly").getObject("Body002"))
Mesh.export(__objs__, u"./STL/OnStepEnclosureAssembly-EnclosureEnclosure Base.stl")
del __objs__
__objs__ = []
__objs__.append(FreeCAD.getDocument("OnStepEnclosureAssembly").getObject("Body004"))
Mesh.export(__objs__, u"./STL/OnStepEnclosureAssembly-EnclosureEnclosure Right.stl")
del __objs__
__objs__ = []
__objs__.append(FreeCAD.getDocument("OnStepEnclosureAssembly").getObject("Body006"))
Mesh.export(__objs__, u"./STL/OnStepEnclosureAssembly-EnclosureEnclosure Left.stl")
del __objs__
__objs__ = []
__objs__.append(FreeCAD.getDocument("OnStepEnclosureAssembly").getObject("Body007"))
Mesh.export(__objs__, u"./STL/OnStepEnclosureAssembly-EnclosureEnclosure Top.stl")
del __objs__
